ISO9541-SN {1 0 9541 2 3} DEFINITIONS ::=
BEGIN

EXPORTS Structured-Name, Owner-Name, Object-Name-Component;

Structured-Name ::= SEQUENCE {
  owner-name          [0] IMPLICIT Owner-Name OPTIONAL,
  -- length restricted to 120 characters
  owner-description   [1]  Message OPTIONAL,
  object-name         [2]  SEQUENCE OF Object-Name-Component OPTIONAL,
  -- length restricted to 100 characters
  object-description  [3]  Message OPTIONAL
}

Owner-Name ::= SEQUENCE {
  objectIdentifier    [0] IMPLICIT OBJECT IDENTIFIER OPTIONAL,
  ownerNameComponent  [1]  SEQUENCE OF Owner-Name-Component OPTIONAL
}

Owner-Name-Component ::= [0]  VisibleString

-- except for "//" and "::"
Object-Name-Component ::= [0]  VisibleString

-- only characters from the following
-- repertoire: "A-Z", "a-z", "0-9",
-- Hyphen, and Period. If the name
-- component is a numeric value, 
-- the first digit is in the range
-- of 1 to 9
Message ::= CHOICE {
  numeric    [0]  NumericString,
  printable  [1]  PrintableString,
  teletex    [2]  TeletexString,
  videotex   [3]  VideotexString,
  visible    [4]  VisibleString,
  ia5        [5]  IA5String,
  graphic    [6]  GraphicString,
  general    [7]  GeneralString
}

END
