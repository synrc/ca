Logical-Descriptors {2 8 1 5 9} DEFINITIONS ::=
BEGIN

EXPORTS
  Logical-Object-Descriptor, Logical-Class-Descriptor, Logical-Object-Type,
    Protection;

IMPORTS
  Object-or-Class-Identifier, Style-Identifier, Resource-Name,
    Construction-Expression, String-Expression
    FROM Identifiers-and-Expressions --  see 7.8 
      
  Comment-String, Binding-Pair, Enciphered, Sealed
    FROM Layout-Descriptors --  see 7.9 
      
  Presentation-Attributes
    FROM Style-Descriptors --  see 7.11
      
  Default-Value-Lists-Logical
    FROM Default-Value-Lists --  see 7.12
      
  Temporal-Relations
    FROM Temporal-Relationships {2 8 1 14 0};

--  See ITU-T Rec. T.424 | ISO/IEC 8613-14
Logical-Object-Descriptor ::= SEQUENCE {
  object-type      Logical-Object-Type OPTIONAL,
  descriptor-body  Logical-Object-Descriptor-Body OPTIONAL
}

Logical-Object-Type ::= INTEGER {
  document-logical-root(0), composite-logical-object(1),
  basic-logical-object(2)}

Logical-Object-Descriptor-Body ::= SET {
  object-identifier        Object-or-Class-Identifier OPTIONAL,
  subordinates             [0] IMPLICIT SEQUENCE OF NumericString OPTIONAL,
  content-portions         [1] IMPLICIT SEQUENCE OF NumericString OPTIONAL,
  object-class             [2] IMPLICIT Object-or-Class-Identifier OPTIONAL,
  presentation-attributes  [6] IMPLICIT Presentation-Attributes OPTIONAL,
  --  only for use for the attribute content-architecture-class;
  --  the content architecture specific attributes can only be referenced by
  --  use of presentation style
  default-value-lists      [7] IMPLICIT Default-Value-Lists-Logical OPTIONAL,
  user-readable-comments   [8] IMPLICIT Comment-String OPTIONAL,
  bindings                 [9] IMPLICIT SET OF Binding-Pair OPTIONAL,
  content-generator        [10] IMPLICIT String-Expression OPTIONAL,
  user-visible-name        [14] IMPLICIT Comment-String OPTIONAL,
  presentation-style       [17] IMPLICIT Style-Identifier OPTIONAL,
  layout-style             [19] IMPLICIT Style-Identifier OPTIONAL,
  protection               [20] IMPLICIT Protection OPTIONAL,
  application-comments     [25] IMPLICIT OCTET STRING OPTIONAL,
  primary                  [27] IMPLICIT Object-or-Class-Identifier OPTIONAL,
  alternative              [28] IMPLICIT Object-or-Class-Identifier OPTIONAL,
  enciphered               [34] IMPLICIT Enciphered OPTIONAL,
  sealed                   [35] IMPLICIT Sealed OPTIONAL,
  temporal-relations       [36] IMPLICIT Temporal-Relations OPTIONAL
}

Logical-Class-Descriptor ::= SEQUENCE {
  object-type      Logical-Object-Type,
  descriptor-body  Logical-Class-Descriptor-Body
}

Logical-Class-Descriptor-Body ::= SET {
  object-class-identifier     Object-or-Class-Identifier,
  generator-for-subordinates  [0]  Construction-Expression OPTIONAL,
  content-portions            [1] IMPLICIT SEQUENCE OF NumericString OPTIONAL,
  presentation-attributes     [6] IMPLICIT Presentation-Attributes OPTIONAL,
  --  only for use for the attribute content-architecture-class;
  --  the content architecture specific attributes can only be referenced by
  --  use of presentation style
  default-value-lists         [7] IMPLICIT Default-Value-Lists-Logical OPTIONAL,
  user-readable-comments      [8] IMPLICIT Comment-String OPTIONAL,
  bindings                    [9] IMPLICIT SET OF Binding-Pair OPTIONAL,
  content-generator           [10] IMPLICIT String-Expression OPTIONAL,
  user-visible-name           [14] IMPLICIT Comment-String OPTIONAL,
  presentation-style          [17] IMPLICIT Style-Identifier OPTIONAL,
  layout-style                [19] IMPLICIT Style-Identifier OPTIONAL,
  protection                  [20] IMPLICIT Protection OPTIONAL,
  resource                    [24] IMPLICIT Resource-Name OPTIONAL,
  application-comments        [25] IMPLICIT OCTET STRING OPTIONAL,
  enciphered                  [34] IMPLICIT Enciphered OPTIONAL,
  sealed                      [35] IMPLICIT Sealed OPTIONAL,
  temporal-relations          [36] IMPLICIT Temporal-Relations OPTIONAL
}

Protection ::= INTEGER {unprotected(0), protected(1)}

END
