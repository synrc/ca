MultipleSignatures-2010
     { iso(1) member-body(2) us(840) rsadsi(113549) pkcs(1) pkcs9(9)
       smime(16) modules(0) id-mod-multipleSign-2009(59) }
   DEFINITIONS IMPLICIT TAGS ::=
   BEGIN
     -- EXPORTS All
     -- The types and values defined in this module are exported for use
     -- in the other ASN.1 modules.  Other applications may use them for
     -- their own purposes.

     IMPORTS

     -- Imports from PKIX-Common-Types-2009 [RFC5912]

     ATTRIBUTE
       FROM PKIX-CommonTypes-2009
           { iso(1) identified-organization(3) dod(6) internet(1)
             security(5) mechanisms(5) pkix(7) id-mod(0)
             id-mod-pkixCommon-02(57)}

     -- Imports from CryptographicMessageSyntax-2010 [RFC6268]

     DigestAlgorithmIdentifier, SignatureAlgorithmIdentifier
       FROM CryptographicMessageSyntax-2010
       { iso(1) member-body(2) us(840) rsadsi(113549)
          pkcs(1) pkcs-9(9) smime(16) modules(0) id-mod-cms-2009(58) }

     -- Imports from ExtendedSecurityServices-2009 [RFC5911]

     ESSCertIDv2
       FROM ExtendedSecurityServices-2009
       { iso(1) member-body(2) us(840) rsadsi(113549) pkcs(1) pkcs-9(9)
         smime(16) modules(0) id-mod-ess-2006-02(42) }
     ;

     --
     -- Section 3.0
     --
     --  at-multipleSignatures should be added ONLY to the
     --    SignedAttributesSet defined in [RFC5652]
     --

     at-multipleSignatures ATTRIBUTE ::= {
       TYPE MultipleSignatures
       IDENTIFIED BY id-aa-multipleSignatures
     }

     id-aa-multipleSignatures OBJECT IDENTIFIER ::= {
       iso(1) member-body(2) us(840) rsadsi(113549) pkcs(1) pkcs9(9)
       id-aa(2) 51 }

     MultipleSignatures ::= SEQUENCE {
       bodyHashAlg     DigestAlgorithmIdentifier,
       signAlg         SignatureAlgorithmIdentifier,
       signAttrsHash   SignAttrsHash,
       cert            ESSCertIDv2 OPTIONAL
     }

     SignAttrsHash ::= SEQUENCE {
       algID            DigestAlgorithmIdentifier,
       hash             OCTET STRING
     }

   END
