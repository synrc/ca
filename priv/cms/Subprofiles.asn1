Subprofiles {2 8 1 12 2} DEFINITIONS IMPLICIT TAGS ::=
BEGIN

EXPORTS Subprofile-Descriptor, Subprofile-Identifier;

IMPORTS
  Character-Data, Date-and-Time, Document-Reference, Personal-Name,
    Originators, Other-User-Information, Local-File-References,
    Security-Information
    FROM Document-Profile-Descriptor {2 8 1 5 6}
  --  see ITU-T Rec. T.415 | ISO/IEC 8613-5
  Location-Expression
    FROM Location-Expressions {2 8 1 12 0};

Subprofile-Descriptor ::= SET {
  subprofile-identifier                    [0]  Subprofile-Identifier,
  subprofile-reference                     [1]  Subprofile-Reference OPTIONAL,
  subprofile-precedence                    [2]  INTEGER OPTIONAL,
  document-fragment-reference              [3]  Location-Expression,
  content-architecture-classes
    [4]  SET OF OBJECT IDENTIFIER OPTIONAL, --  shall always
  
  --  be present, except when used in a location expression
  document-fragment-management-attributes
    [5]  Document-Fragment-Management-Attributes OPTIONAL
}

Subprofile-Identifier ::= [APPLICATION 8]  PrintableString

--  only digits and spaces are used in the present version of this Specification;
--  other characters are reserved for extensions
Subprofile-Reference ::= CHOICE {
  unique-reference       [0]  OBJECT IDENTIFIER,
  descriptive-reference  [1]  Character-Data
}

Document-Fragment-Management-Attributes ::= SET {
  document-fragment-description  [0]  Document-Fragment-Description OPTIONAL,
  dates-and-times                [1]  Dates-and-Times OPTIONAL,
  originators                    [2]  Originators OPTIONAL,
  other-user-information         [3]  Other-User-Information OPTIONAL,
  external-references            [4]  External-References2 OPTIONAL,
  local-file-references          [5]  Local-File-References OPTIONAL,
  languages                      [6]  SET OF Character-Data OPTIONAL,
  security-information           [7]  Security-Information OPTIONAL
}

Document-Fragment-Description ::= SET {
  title                   [0]  Character-Data OPTIONAL,
  subject                 [1]  Character-Data OPTIONAL,
  document-fragment-type  [2]  Character-Data OPTIONAL,
  abstract                [3]  Character-Data OPTIONAL,
  keywords                [4]  SET OF Character-Data OPTIONAL
}

Dates-and-Times ::= SET {
  document-fragment-date-and-time  [0]  Date-and-Time OPTIONAL,
  creation-date-and-time           [1]  Date-and-Time OPTIONAL,
  local-filing-date-and-time       [2]  SEQUENCE OF Date-and-Time OPTIONAL,
  expiry-date-and-time             [3]  Date-and-Time OPTIONAL,
  start-date-and-time              [4]  Date-and-Time OPTIONAL,
  purge-date-and-time              [5]  Date-and-Time OPTIONAL,
  release-date-and-time            [6]  Date-and-Time OPTIONAL,
  revision-history
    [7]  SEQUENCE OF
           SET {revision-date-and-time  [0]  Date-and-Time OPTIONAL,
                version-identifier      [1]  Character-Data OPTIONAL,
                revisers
                  [2]  SET OF
                         SET {names         [0]  SET OF Personal-Name OPTIONAL,
                              position      [1]  Character-Data OPTIONAL,
                              organization  [2]  Character-Data OPTIONAL
                         } OPTIONAL,
                version-reference
                  [3]  Document-or-Document-Fragment-Reference OPTIONAL,
                user-comments           [4]  Character-Data OPTIONAL} OPTIONAL
}

External-References2 ::= SET {
  references-to-other-documents-or-document-fragments
    [0]  SET OF Document-or-Document-Fragment-Reference OPTIONAL,
  superseded-documents-or-document-fragments
    [1]  SET OF Document-or-Document-Fragment-Reference OPTIONAL
}

Document-or-Document-Fragment-Reference ::= CHOICE {
  document           [0]  Document-Reference,
  document-fragment  [1]  Subprofile-Reference
}

END
